FME workspace Weather_Data_Json_to_Postgis.fmw

Parameters:
- SourceDataset_GEOJSON = $(FME_MF_DIR)Weather_Data_all_20200109T140000Z.json   # Source GeoJSON File or URL
- DestDataset_POSTGRES = Helsinki_osm   # Connection

Readers:
- GEOJSON_1: GEOJSON from $(SourceDataset_GEOJSON)

Writers:
- POSTGRES_1: POSTGRES to $(DestDataset_POSTGRES)

Weather_Data_all_20200109T140000Z (reader GEOJSON_1)
    attributes: observationType string, timestep{} string, id string, observedPropertyName string, result{} int
    -> ListExploder
ListExploder
    ATTR_ACCUM_MODE = Merge List Attributes
    ATTR_CONFLICT_RES = Use List Attribute Values
    INDEX_ATTR = _element_index
    LIST_ATTR = timestep{}
    ELEMENTS -> ListExploder_2
    <REJECTED> -> FeatureReader__Rejected_
ListExploder_2
    ATTR_ACCUM_MODE = Merge List Attributes
    ATTR_CONFLICT_RES = Use List Attribute Values
    INDEX_ATTR = _element_index
    LIST_ATTR = result{}
    ELEMENTS -> GeometryExtractor
    <REJECTED> -> FeatureReader__Rejected_
GeometryExtractor
    ATTR = _geometry
    JSON_MAX_DIGITS = 7
    KIND_LONG = GeoJSON
    OGCVERSION = 1.2
    OGC_WKT_PRECISION_DISPLAY = 64-bit
    OGEOSMS_URL_PREFIX = http://maps.google.com/?q=
    PREFER_POLYGON_OVER_SURFACE = No
    REMOVE_GEOMETRY = No
    -> DuplicateFilter
    -> AttributeRenamer
    <REJECTED> -> FeatureReader__Rejected_
AttributeRenamer
    ATTR_TABLE = RENAME_SET_DEFAULT _geometry > _ori_geometry
    -> FeatureMerger [REQUESTOR]
DuplicateFilter
    INPUT_ORDERED_CHOICE = No
    KEYATTR = _geometry
    UNIQUE -> GUIDGenerator
GUIDGenerator
    -> FeatureWriter [OUTPUT]
FeatureWriter
    DATASET = Helsinki_osm
    DATASET_ATTR = _dataset
    FEATURE_TYPE_LIST_ATTR = _feature_type
    FORMAT = POSTGIS
    POSTGIS_BULK_COPY = YES
    POSTGIS_COORDINATE_SYSTEM_GRANULARITY = FEATURE_TYPE
    POSTGIS_GENERIC_GEOMETRY = yes
    POSTGIS_INSERT_TEXT_GEOMETRY = NO
    POSTGIS_LOWERCASE_ATTRIBUTE_NAMES = Yes
    POSTGIS_NAMED_CONNECTION = Helsinki_osm
    POSTGIS_SPATIAL_COLUMN_NAME = geom
    POSTGIS_SPATIAL_COLUMN_TYPE = geometry
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> FeatureReader [INITIATOR]
FeatureReader
    ATTRIBUTES = public.weather_data_stations,gfid
    ATTR_ACCUM_MODE = Only Use Result
    COMBINE_GEOM = Use Result
    DATASET = Helsinki_osm
    FEATURETYPES = public.weather_data_stations
    FORMAT = POSTGIS
    INTERACT = <No Spatial Filter>
    OUTPUT_FEATURES_DISPLAY = Schema and Data Features
    POSTGIS_DISABLE_COLLECTION_SPLITTING = yes
    POSTGIS_FEATURES_PER_FETCH = 10000
    POSTGIS_NAMED_CONNECTION = Helsinki_osm
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.weather_data_stations -> GeometryExtractor_2
    <REJECTED> -> FeatureReader__Rejected_
GeometryExtractor_2
    ATTR = _geometry
    JSON_MAX_DIGITS = 7
    KIND_LONG = GeoJSON
    OGCVERSION = 1.2
    OGC_WKT_PRECISION_DISPLAY = 64-bit
    OGEOSMS_URL_PREFIX = http://maps.google.com/?q=
    PREFER_POLYGON_OVER_SURFACE = No
    REMOVE_GEOMETRY = No
    -> FeatureMerger [SUPPLIER]
    <REJECTED> -> FeatureReader__Rejected_
FeatureMerger
    ATTR_ACCUM_MODE = Merge Supplier
    ATTR_CONFLICT_RES = Use Requestor
    GEOM_TYPE = Build Aggregates
    IGNORE_NULLS = No
    JOIN_KEYS = @Value(_ori_geometry) @Value(_geometry) AUTO
    MERGE_TYPE = Attributes Only
    PROCESS_DUPS = YES
    REJECT_NULL_MISSING_KEYS = No
    SUPPLIERS_FIRST = No
    MERGED -> GeometryRemover
    <REJECTED> -> FeatureReader__Rejected_
FeatureReader__Rejected_: Inspector
GeometryRemover
    -> weather_data (writer POSTGRES_1)
weather_data (writer POSTGRES_1)
    attributes: observedpropertyname text, timestep varchar(200), result varchar(200), gfid varchar(200)

FME custom transformer GUIDGenerator
Creates an ESRI GUID ID by creating a UUID enclosed by curly {}.
Input Ports
    Input
Accepts all types of features
    Output Ports
    Output
Returns all features with an additional GFID attribute

INPUT (input)
    -> UUIDGENERATOR_2
Note: Create UUID
UUIDGENERATOR_2: UUIDGenerator
    UUID_ATTR = GFID
    -> CONCATENATOR_2
Note: Enclose the UUID by {}
CONCATENATOR_2: StringConcatenator
    ACTION = Create New Attribute
    PARM_LINE = {@Value(GFID)}
    VAL_ATTR = GFID
    -> OUTPUT (output)
OUTPUT (output)
