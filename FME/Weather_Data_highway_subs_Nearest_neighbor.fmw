FME workspace Weather_Data_highway_subs_Nearest_neighbor.fmw

Parameters:
- SourceDataset_POSTGIS = helsinki_full   # Connection
- SourceDataset_POSTGIS_3 = Helsinki_osm   # Connection
- DestDataset_POSTGIS_2 = helsinki_full   # Connection

Readers:
- POSTGIS_1: POSTGIS from $(SourceDataset_POSTGIS)
- POSTGIS_2: POSTGIS from $(SourceDataset_POSTGIS_3)

Writers:
- POSTGIS_4: POSTGIS to $(DestDataset_POSTGIS_2)

highways_subs (reader POSTGIS_1)
    attributes: osm_id int8, highway text, junction text, motorcar text, foot text, bicycle text, paved text, surface text, tracktype text, barrier text, bridge text, tunnel text, construction text, oneway text, service text, access text, toll text, tourism text, name text, route text, z_order int4, way_area float4, tags text, source int4, target int4, id int4, length float8, asc float8
    -> NeighborFinder [BASE]
weather_data_stations (reader POSTGIS_2)
    attributes: gfid varchar(200)
    -> Reprojector
Reprojector
    DEST = EPSG:3067
    INTERPOLATION_TYPE_NAME = Nearest Neighbor
    RASTER_CELL_SIZE = Preserve Cells
    RASTER_TOLERANCE = 0.0
    SOURCE = Read from feature
    REPROJECTED -> NeighborFinder [CANDIDATE]
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> highways_subs_with_station (writer POSTGIS_4)
highways_subs_with_station (writer POSTGIS_4)
    attributes: osm_id int8, highway text, junction text, motorcar text, foot text, bicycle text, paved text, surface text, tracktype text, barrier text, bridge text, tunnel text, construction text, oneway text, service text, access text, toll text, tourism text, name text, route text, z_order int4, way_area float4, tags text, source int4, target int4, id int4, length float8, asc float8, gfid varchar(200), _distance varchar(200),
      _angle varchar(200), _candidate_angle varchar(200), _candidate_label_angle varchar(200), _closest_candidate_x varchar(200), _closest_candidate_y varchar(200), _closest_base_x varchar(200), _closest_base_y varchar(200)
